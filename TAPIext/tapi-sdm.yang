module tapi-sdm {
    namespace "urn:onf:otcc:yang:tapi-sdm";
    prefix tapi-sdm;
    import tapi-common {
        prefix tapi-common;
    }
    import tapi-connectivity {
        prefix tapi-connectivity;
    }
    import tapi-topology {
        prefix tapi-topology;
    }
    import tapi-photonic-media {
        prefix tapi-photonic-media;
    }
    organization "CTTC";
    contact "";
    description "
        This module contains TAPI SDM Model definitions.
        ";
    revision 2019-06-19 {
        description "Based on ONF Transport API version 2.1.1.
                   Changes included in this TAPI release (v2.1.1) are listed in
                   <https://github.com/OpenNetworkingFoundation/TAPI/blob/develop/CHANGE_LOG/change-log.2.1.1.md>";
        reference "ONF-TR-527, ONF-TR-512, ONF-TR-531, RFC 7950, RFC 6087 and ONF TAPI UML model
                  <https://github.com/OpenNetworkingFoundation/TAPI/tree/v2.1.0/UML>";
    }
    augment "/tapi-common:context/tapi-topology:topology-context/tapi-topology:topology/tapi-topology:node/tapi-topology:owned-node-edge-point" {
        container sdm-node-edge-point-spec {
            uses sdm-node-edge-point-spec;
            description "Augments the base LayerProtocol information in NodeEdgePoint with SDM-specific information";
        }
        description "Augments the base LayerProtocol information in NodeEdgePoint with SDM-specific information";
    }
    augment "/tapi-common:context/tapi-common:service-interface-point" {
        container sdm-service-interface-point-spec {
            uses sdm-service-interface-point-spec;
            description "none";
        }
        description "none";
    }
    augment "/tapi-common:context/tapi-connectivity:connectivity-context/tapi-connectivity:connectivity-service/tapi-connectivity:end-point" {
        container sdm-service-interface-point-spec {
            uses sdm-service-interface-point-spec;
            description "none";
        }
        description "none";
    }
    augment "/tapi-common:context/tapi-topology:topology-context/tapi-topology:topology/tapi-topology:node/tapi-topology:owned-node-edge-point/tapi-connectivity:cep-list/tapi-connectivity:connection-end-point" {
        container sdm-connection-end-point-spec {
            uses sdm-connection-end-point-spec;
            description "none";
        }
        description "none";
    }
    augment "/tapi-common:context/tapi-connectivity:connectivity-context/tapi-connectivity:connectivity-service" {
        uses include-core;
    }

   /**************************
    * package object-classes
    **************************/
    grouping include-core {
        container include-core{
            uses sdm-properties-pac;
        }
    }
    grouping sdm-pool-capability-pac {
        list available-core {
            key 'core-id';
            config false;
            uses sdm-core-pac;
            description "none";
        }
        container available-transceiver {
            uses available-transceiver;
        }
    }
    grouping sdm-core-pac {
        leaf core-id {
            type uint64;
            description "none";
        }
        list available-mode {
            key "mode-id";
            uses sdm-mode-pac;
            description "none";
        }
    }
    grouping sdm-mode-pac {
        leaf mode-id {
            type uint64;
            description "none";
        }
        uses tapi-photonic-media:media-channel-pool-capability-pac;
    }
    grouping available-transceiver {
        leaf transceiver-id {
            type string;
        }
        leaf transceiver-type {
            type string;
        }
        list core_mode_ref {
            key "core_mode_ref";
            leaf core_mode_ref {
                type uint64;
            }
            list core-id {
                key "core-id";
                leaf core-id {
                    type uint64;
                }
            }
            list mode-id {
                key "mode-id";
                leaf mode-id {
                    type uint64;
                }
            }
        }
        /**leaf supported-modulation-format {
            type tapi-photonic-media:modulation-technique;
        }*/
        leaf supportable-slices {
            type uint64;
        }
        container supportable-spectrum {
            uses tapi-photonic-media:spectrum-band;
        }
        container supported-bandwidth {
            container max-bw {
              uses tapi-common:capacity-value;
            }
            container min-bw {
              uses tapi-common:capacity-value;
            }
        }
        /**leaf supported-FEC {
            type string;
        }
        leaf supported-equalization {
            type string;
        }
        leaf supported-monitoring {
            type string;
        }*/
    }
    grouping sdm-node-edge-point-spec {
        container sdm-pool {
            config false;
            uses sdm-pool-capability-pac;
            description "none";
        }
        description "none";
    }

    grouping sdm-properties-pac {
        leaf core-id {
            type uint64;
        }
        container occupied-spectrum {
            uses tapi-photonic-media:spectrum-band;
            description "none";
        }
        description "none";
    }
 
    grouping sdm-service-interface-point-spec {
        container sdm-pool {
            config false;
            uses sdm-pool-capability-pac;
            description "none";
        }
        description "none";
    }
   
    grouping sdm-connection-end-point-spec {
        container sdm {
            config false;
            uses sdm-properties-pac;
            description "none";
        }
        description "none";
    }

   
   /**************************
    * package type-definitions
    **************************/
    identity SDM_LAYER_QUALIFIER {
        base tapi-common:LAYER_PROTOCOL_QUALIFIER;
        description "none";
    }

    typedef sdm-layer-qualifier {
        type identityref {
            base SDM_LAYER_QUALIFIER;
        }
        description "none";
    }

    
}
